module vpnintent-impl {
    yang-version 1;
    namespace "urn:opendaylight:params:xml:ns:yang:vpnintent:impl";
    prefix "vpnintent-impl";

    import config { prefix config; revision-date 2013-04-05; }
    import opendaylight-md-sal-binding { prefix md-sal-binding; revision-date 2013-10-28;}

    description
        "Service definition for vpnintent project";

    revision "2014-12-10" {
        description
            "Initial revision";
    }

    identity vpnintent-impl {
        base config:module-type;
        config:java-name-prefix VpnintentImpl;
    }

    augment "/config:modules/config:module/config:configuration" {
        case vpnintent-impl {
            when "/config:modules/config:module/config:type = 'vpnintent-impl'";
            container broker {
                uses config:service-ref {
                    refine type {
                        mandatory true;
                        config:required-identity md-sal-binding:binding-broker-osgi-registry;
                    }
                }
            }
            container rpc-registry {
                uses config:service-ref {
                    refine type {
                        mandatory true;
                        config:required-identity md-sal-binding:binding-rpc-registry;
                    }
                }
            }
        }
    }
}
