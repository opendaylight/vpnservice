module vpnservice-dhcp {
    namespace "urn:opendaylight:vpnservice:dhcp";
    prefix "dhcp";

    import ietf-inet-types {
        prefix inet;
        revision-date "2013-07-15";
    }

    revision "2016-04-28" {
        description "It provides required datastore containers to handle DHCP requests
                     coming from access or external tunnel ports";
    }

    container designated-switches-for-external-tunnels {
        config true;
        description "contains designated dataplane-node-identifier which handles DHCP requests for each external tunnel";
        list designated-switch-for-tunnel {
            key "tunnel-remote-ip-address elan-instance-name";
            leaf tunnel-remote-ip-address {
                description "remote end point ip address of external tunnel";
                type inet:ip-address;
            }
            leaf elan-instance-name {
                description "elan name indicates l2 network domain";
                type string;
            }
            leaf dpId {
                description "contains dataplane-node-identifier";
                type int64;
            }
        }
    }
}
